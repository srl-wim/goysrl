module srl_nokia-bridge-table-mac-learning-entries {

  yang-version "1.1";

  // namespace
  namespace "urn:srl_nokia/network-instance/bridge-table/mac-learning/mac-learning-entries";

  prefix "srl_nokia-bridge-table-mac-learning-entries";

  import srl_nokia-common { prefix srl_nokia-comm; }
  import srl_nokia-network-instance { prefix srl_nokia-netinst; }
  import srl_nokia-bridge-table { prefix srl_nokia-bridge-table; }
  import srl_nokia-bridge-table-mac-learning { prefix srl_nokia-bridge-table-mac-learning; }

  description
    "This yang file gives a description of bridge table configuration.";

  revision 2020-06-30 {
    description
      "SRLinux 20.6.1";
  }

  grouping bridge-table-mac-learning-entries-top {
    container learnt-entries {
      config false;
      list mac {
        config false;
        key "address";
        description "macs learnt on the bridging instance";
        leaf address {
          type srl_nokia-comm:mac-address;
        }

        leaf destination {
          type string;
          description
            "the name of the subinterface where the mac is learnt against.";
        }

        leaf last-update {
          type srl_nokia-comm:date-and-time-delta;
          description
            "The date and time of the last update of this learnt mac";
        }

        leaf aging {
          type union {
            type uint64;
            type enumeration {
              enum "disabled"  { value -1; }
            }
          }
          units "seconds";
          description 
            "remaining age time for learnt macs";
        }     
      }   
    }
  }

  augment "/srl_nokia-netinst:network-instance/srl_nokia-netinst:bridge-table/srl_nokia-netinst:mac-learning" {
    uses bridge-table-mac-learning-entries-top;
  }
}

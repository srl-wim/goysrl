module srl_nokia-qos {
  yang-version 1.1;
  namespace "urn:srl_nokia/qos";
  prefix "srl_nokia-qos";

  import srl_nokia-common {
      prefix srl_nokia-comm;
  }
  import srl_nokia-interfaces {
      prefix srl_nokia-if;
  }
  import srl_nokia-features {
      prefix srl-feat;
  }
  
  revision 2020-06-30 {
    description
      "SRLinux 20.6.1";
  }
  revision 2019-11-30 {
    description
      "SRLinux 19.11.1";
  }

  typedef traffic-class {
    type uint8 {
      range "0..7";
    }
  }

  typedef forwarding-class {
    type enumeration {
      enum "fc0";
      enum "fc1";
      enum "fc2";
      enum "fc3";
      enum "fc4";
      enum "fc5";
      enum "fc6";
      enum "fc7";
    }
  }

  typedef dscp-name {
    type enumeration {
        enum "CS0" {
            value 0;
        }
        enum "LE" {
            value 1;
            reference
              "RFC 8622";
        }
        enum "CS1" {
            value 8;
        }
        enum "AF11" {
            value 10;
        }
        enum "AF12" {
            value 12;
        }
        enum "AF13" {
            value 14;
        }
        enum "CS2" {
            value 16;
        }
        enum "AF21" {
            value 18;
        }
        enum "AF22" {
            value 20;
        }
        enum "AF23" {
            value 22;
        }
        enum "CS3" {
            value 24;
        }
        enum "AF31" {
            value 26;
        }
        enum "AF32" {
            value 28;
        }
        enum "AF33" {
            value 30;
        }
        enum "CS4" {
            value 32;
        }
        enum "AF41" {
            value 34;
        }
        enum "AF42" {
            value 36;
        }
        enum "AF43" {
            value 38;
        }
        enum "CS5" {
            value 40;
        }
        enum "EF" {
            value 46;
        }
        enum "CS6" {
            value 48;
        }
        enum "CS7" {
            value 56;
        }
    }
  }

  grouping qos-top {
    description
      "Top-level grouping for QoS model";

    container qos {
      if-feature "srl-feat:jericho2 or srl-feat:platform-7220-d2 or srl-feat:platform-7220-d3";
      description
        "Top-level container for QoS data";
      uses qos-classifier-top;
      uses qos-rewrite-top;
    }
  }

  grouping qos-classifier-top {
    description
      "Top-level grouping for classifier data";

    container classifiers {
      uses dscp-classifier;
      uses mpls-tc-classifier;
    }
  }

  grouping dscp-classifier {
    list dscp-policy {
      key name;
      leaf name {
        type srl_nokia-comm:name;
        description
          "User-configured name for a DSCP classification policy

          The name 'default' is reserved for the system default DSCP classifier.";
      }
      list dscp {
        key value;
        leaf value {
          type uint8 {
            range "0..63";
          }
          description
            "DSCP codepoint value, expressed as a number in the range 0-63";
        }
        leaf forwarding-class {
          type forwarding-class;
          description
            "The forwarding class to which the DSCP value is mapped";
        }
      }
    }
  }

  grouping mpls-tc-classifier {
    list mpls-traffic-class-policy {
      key name;
      leaf name {
        type srl_nokia-comm:name;
        description
          "User-configured name for an MPLS traffic-class classification policy

          The name 'default' is reserved for the system default MPLS TC classifier.";
      }
      list traffic-class {
        key value;
        leaf value {
          type traffic-class;
          description
            "A single traffic-class value";
        }
        leaf forwarding-class {
          type forwarding-class;
          description
            "The forwarding class to which the traffic-class value is mapped";
        }
      }
    }
  }

  grouping qos-rewrite-top {
    description
      "Top-level grouping for traffic marking (rewrite) policies";

    container rewrite-rules {
      uses dscp-rewrite;
      uses mpls-tc-rewrite;
    }
  }

  grouping dscp-rewrite {
    list dscp-policy {
      key name;
      leaf name {
        type srl_nokia-comm:name;
        description
          "User-configured name for a DSCP rewrite policy.";
      }
      list map {
        key forwarding-class;
        leaf forwarding-class {
          type forwarding-class;
          description
            "The forwarding-class value";
        }
        leaf dscp {
          type union {
            type uint8 {
              range "0..63";
            }
            type dscp-name;
          }
        }
      }
    }
  }

  grouping mpls-tc-rewrite {
    list mpls-traffic-class-policy {
      key name;
      leaf name {
        type srl_nokia-comm:name;
        description
          "User-configured name for an MPLS traffic-class rewrite policy.";
      }
      list map {
        key forwarding-class;
        leaf forwarding-class {
          type forwarding-class;
          description
            "The forwarding-class value";
        }
        leaf traffic-class {
          type traffic-class;
          description
            "The MPLS traffic class value to mark the packet with";
        }
      }
    }
  }

  grouping interface-qos {
    container qos {
      if-feature "srl-feat:jericho2 or srl-feat:platform-7220-d2 or srl-feat:platform-7220-d3";
      container output {
        list unicast-queue {
          description
            "List of unicast queues";

          key "queue-id";

          leaf queue-id {
              type srl_nokia-comm:queue-index;
              description
                "The queue identifier
                 
                 This has a one-to-one mapping to forwarding class.";
          }
          container queue-parameters {
            leaf peak-rate-percent {
                type uint8 {
                    range "1..100";
                }
                default 100;
                description
                  "The maximum percentage of port bandwidth that is available to the traffic in this unicast queue. The default is 100.";
            }
            leaf peak-rate-bps {
              config false;
              type uint64;
              description
                "The actual/operational peak rate in bits per second.";
            }
            leaf strict-priority {
              type boolean;
              default true;
              description
                "When set to true the unicast queue is serviced as a strict priority queue, regardless of whether a weight is configured or its value.
                 
                 When set to false the unicast queue is serviced using WRR, even if the queue does not have a configured weight; in this case the default weight value of 1 is used.
                 
                 On 7220 IXR-D2 and 7220 IXR-D3 (Trident3 based) systems this setting also applies to the multicast queue for the same FC. To be more specific, the choice to use strict priority vs WRR applies to the scheduler node attached to the queue pair.";
            }
            leaf weight {
              type uint64 {
                range "1..255";
              }
              default 1;
              description
                "Configures the relative weight of a round-robin queue.
                 
                 On 7220 IXR-D2 and 7220 IXR-D3 (Trident3 based) systems this setting also applies to the multicast queue for the same FC. To be more specific, the WRR weight applies to the scheduler node attached to the queue pair.";
            }
          }
          // list multicast-queue
        }
      }
    }
  }

  grouping queue-stats {
      container queue-statistics {
          if-feature "srl-feat:jericho2 or srl-feat:platform-7220-d2 or srl-feat:platform-7220-d3";
          config false;
            list unicast-queue {
              description
                  "List of unicast queues.";

              key "queue-id";

              leaf queue-id {
                  type srl_nokia-comm:queue-index;
                  description
                      "The queue identifier
                     
                       This has a one-to-one mapping to forwarding class.";
              }
              leaf transmitted-packets {
                  type srl_nokia-comm:zero-based-counter64;
                  description
                      "Number of packets transmitted by the egress queue, including transit traffic and locally-originated traffic. This measures packets transmitted on the wire after drops in the VOQ queues, drops done by ACL entries and final drops by the EGQ itself (e.g. due to header compensation issues).";
              }
              leaf transmitted-octets {
                  type srl_nokia-comm:zero-based-counter64;
                  description
                      "Number of octets transmitted by the unicast queue.";
              }
              leaf final-dropped-packets {
                  type srl_nokia-comm:zero-based-counter64;
                  description
                      "Number of packets dropped by the unicast queue.
                       
                       On 7250-IXR (Jericho2-based) systems unicast packet drops related to egress port congestion should show up in the VOQ stats and not in this statistic.";
              }
              leaf final-dropped-octets {
                  type srl_nokia-comm:zero-based-counter64;
                  description
                      "Number of octets in packets dropped by the egress queue itself.";
              }
              list virtual-output-queue {
                  if-feature "srl-feat:jericho2";
                  description
                      "List of virtual output queues that can send traffic to this egress queue. The list always has one entry for each IMM slot in the chassis, even if one or more slots are empty.";
                  key slot;
                  leaf slot {
                      type uint8 {
                          range "1..8";
                      }
                      description
                          "The slot identifier for the virtual output queue.";
                  }
                  leaf forwarded-packets {
                      type srl_nokia-comm:zero-based-counter64;
                      description
                          "The number of packets transmitted from the VOQ to the egress queue. This reads 0 when the IMM associated with the VOQ is not inserted and it resets to 0 whenever the IMM associated with the VOQ is removed.";
                  }
                  leaf forwarded-octets {
                      type srl_nokia-comm:zero-based-counter64;
                      description
                          "The number of octets in packets transmitted from the VOQ to the egress queue.";
                  }
                  leaf dropped-packets {
                      type srl_nokia-comm:zero-based-counter64;
                      description
                          "The number of unicast packets dropped in the VOQ due to congestion at the egress port/queue. This reads 0 when the IMM associated with the VOQ is not inserted and it resets to 0 whenever the IMM associated with the VOQ is removed.";
                  }
                  leaf dropped-octets {
                      type srl_nokia-comm:zero-based-counter64;
                      description
                          "The number of octets in unicast packets dropped in the VOQ due to congestion at the egress port/queue. This reads 0 when the IMM associated with the VOQ is not inserted and it resets to 0 whenever the IMM associated with the VOQ is removed.";
                  }
              }
              leaf last-clear {
                  type srl_nokia-comm:date-and-time-delta;
                  description
                      "Timestamp of the last time the queue statistics were cleared";
              }
          }
          list multicast-queue {
              description
                "List of multicast queues.";

              key "queue-id";

              leaf queue-id {
                  type srl_nokia-comm:queue-index;
                  description
                    "The queue identifier
                     
                     This has a one-to-one mapping to forwarding class.";
              }
              leaf last-clear {
                  type srl_nokia-comm:date-and-time-delta;
                  description
                    "Timestamp of the last time the statistics associated with this multicast queue were cleared";
              }
              leaf transmitted-packets {
                  type srl_nokia-comm:zero-based-counter64;
                  description
                    "Number of packets transmitted by the multicast queue.";
              }
              leaf transmitted-octets {
                  type srl_nokia-comm:zero-based-counter64;
                  description
                    "Number of octets transmitted by the multicast queue.";
              }
              leaf final-dropped-packets {
                  type srl_nokia-comm:zero-based-counter64;
                  description
                    "Number of packets dropped by the multicast queue.";
              }
              leaf final-dropped-octets {
                  type srl_nokia-comm:zero-based-counter64;
                  description
                    "Number of octets dropped by the multicast queue.";
              }
          }
      }
  }

  grouping subinterface-qos {
    container qos {
      if-feature "srl-feat:jericho2 or srl-feat:platform-7220-d2 or srl-feat:platform-7220-d3";
      container input {
        container classifiers {
          leaf ipv4-dscp {
              if-feature "srl-feat:jericho2";
              type leafref {
                  path "/srl_nokia-qos:qos/srl_nokia-qos:classifiers/srl_nokia-qos:dscp-policy/name";
              }
              description
                "Reference to the name of a DSCP classifier policy that applies only to IPv4 traffic.";
          }
          leaf ipv6-dscp {
              if-feature "srl-feat:jericho2";
              type leafref {
                  path "/srl_nokia-qos:qos/srl_nokia-qos:classifiers/srl_nokia-qos:dscp-policy/name";
              }
              description
                "Reference to the name of a DSCP classifier policy that applies only to IPv6 traffic.";
          }
          leaf dscp {
              if-feature "srl-feat:platform-7220-d2 or srl-feat:platform-7220-d3";
              type leafref {
                  path "/srl_nokia-qos:qos/srl_nokia-qos:classifiers/srl_nokia-qos:dscp-policy/name";
              }
              description
                "Reference to the name of a DSCP classifier policy that applies to both IPv4 and IPv6 traffic.";
          }

          leaf mpls-traffic-class {
            type leafref {
                path "/srl_nokia-qos:qos/srl_nokia-qos:classifiers/srl_nokia-qos:mpls-traffic-class-policy/name";
            }            
            description "Reference to the name of an MPLS traffic-class classifier policy";
          }
        }
      }
      container output {
        container rewrite-rules {
          leaf ipv4-dscp {
              if-feature "srl-feat:jericho2";
              type leafref {
                  path "/srl_nokia-qos:qos/srl_nokia-qos:rewrite-rules/srl_nokia-qos:dscp-policy/name";
              }
              description
                "Reference to the name of a DSCP rewrite-rule policy that applies only to IPv4 traffic.";
          }
          leaf ipv6-dscp {
              if-feature "srl-feat:jericho2";
              type leafref {
                  path "/srl_nokia-qos:qos/srl_nokia-qos:rewrite-rules/srl_nokia-qos:dscp-policy/name";
              }
              description
                "Reference to the name of a DSCP rewrite-rule policy that applies only to IPv6 traffic.";
          }
          leaf dscp {
              if-feature "srl-feat:platform-7220-d2 or srl-feat:platform-7220-d3";
              type leafref {
                  path "/srl_nokia-qos:qos/srl_nokia-qos:rewrite-rules/srl_nokia-qos:dscp-policy/name";
              }
              description
                "Reference to the name of a DSCP rewrite-rule policy that applies to both IPv4 and IPv6 traffic.";
              must "../../../../type != 'srl_nokia-if:bridged'" {
                  error-message "rewrite-rules not allowed with type bridged";
              }
          }

          leaf mpls-traffic-class {
            type leafref {
                path "/srl_nokia-qos:qos/srl_nokia-qos:rewrite-rules/srl_nokia-qos:mpls-traffic-class-policy/name";
            }            
            description "Reference to the name of an MPLS traffic-class rewrite-rule policy";
          }
        }
      }
    }
  }

  uses qos-top;

  augment "/srl_nokia-if:interface" {
      uses interface-qos;
      uses queue-stats;
  }

  augment "/srl_nokia-if:interface/srl_nokia-if:subinterface" {
      uses subinterface-qos;
  }

}

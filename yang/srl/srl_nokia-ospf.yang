module srl_nokia-ospf {
    yang-version "1.1";

    namespace "urn:srl_nokia/ospf";

    prefix "srl_nokia-ospf";

    import ietf-yang-types { prefix "yang"; }
    import srl_nokia-common { prefix srl_nokia-comm; }
    import srl_nokia-system { prefix srl_nokia-system; }
    import srl_nokia-keychains { prefix srl_nokia-keychains; }
    import srl_nokia-network-instance { prefix srl_nokia-netinst; }
    import srl_nokia-routing-policy { prefix srl-rpol; }
    import srl_nokia-ospf-types { prefix srl_nokia-ospf-types; }

    include srl_nokia-ospf-lsdb;
    include srl_nokia-ospfv3-lsas;

    description
        "This yang file models configuration and state of the OSPFv2 protocol";

    // Groupings

  revision 2020-06-30 {
    description
      "SRLinux 20.6.1";
  }

    grouping ospf-interface-key {
        leaf interface-name {
            description
                "Router logical interface name.";
            type leafref {
                // ref to names of net-instance interfaces
                path "../../../../../../srl_nokia-netinst:interface/srl_nokia-netinst:name";
                // path:
                // net-inst/protocols/ospf/instance/area/interface/interface-name
            }
        }
    }

    grouping ospf-neighbor-state {
        list neighbor {
            config false;
            description
                "List of neighbors associated with this OSPF interface";
            key router-id;

            leaf router-id{
                description
                    "The router-id advertised by the neighbor";
                type yang:dotted-quad;
            }

            leaf priority {
                description
                    "Router priority advertised by neighbor";
                type uint8;
            }

            leaf dead-time {
                description
                    "The remaining number of seconds remaining in the neighbor's dead time interval";
                type uint32;
            }

            leaf designated-router {
                description
                    "Advertised designated router";
                type yang:dotted-quad;
            }

            leaf backup-designated-router {
                description
                    "Advertised backup designated router";
                type yang:dotted-quad;
            }

            leaf optional-capabilities {
                description
                    "Advertised Optional Capabilities";
                type yang:hex-string;
            }

            leaf last-established-time {
                description
                    "Time then OSPF neighbor was last established";
                type srl_nokia-comm:timeticks64;
            }

            leaf adjacency-state {
                description
                    "Current OSPF Neighbor state";
                type identityref {
                    base srl_nokia-ospf-types:OSPF_NEIGHBOR_STATE;
                }
            }

            leaf state-changes {
                description
                    "total numer of OSPF state changes";
                type uint32;
            }

            leaf retransmission-queue-length {
                type uint32;
            }
        }

    }

    grouping ospf-interface-config {
        leaf advertise-router-capability {
            type boolean;
            default "true";
            description "Allow router advertisement capabilities";
        }
        leaf admin-state {
            type srl_nokia-comm:admin-state;
            default "enable";
            description "Administrative state of the OSPF";
        }
        leaf advertise-subnet {
            type boolean;
            default "true";
            description "Advertise point-to-point interfaces as subnet routes";
        }

        leaf interface-type {
            type srl_nokia-ospf-types:interface-type;
            //sros-ext:immutable;
            description "Interface type to broadcast or point-to-point";
        }

        leaf lsa-filter-out {
            type srl_nokia-ospf-types:lsa-filter-out;
            default "none";
            description "LSA flooding reduction";
        }

        leaf metric {
            type srl_nokia-ospf-types:ospf-metric;
            description "Explicit route cost metric that is applied to the interface";
        }

        leaf mtu {
            type uint32 {
                range "512..9198";
            }
            description "MTU for the OSPF to use on the interface";
        }

        leaf passive {
            description
              "Allow interface to be advertised as an OSPF interface without running the OSPF protocol";
            type boolean;
        }

        leaf priority {
            description
              "Priority of the interface to apply in the designated router election on the subnet";
            type uint16 {
                range "0..255";
          }
            default "1";
        }

        leaf hello-interval {
            type uint32 {
                range "1..65535";
            }
            units "seconds";
            default "10";
            description "Time between OSPF Hellos of this interface";
        }

        leaf dead-interval {
            type uint32 {
                range "2..65535";
            }
            units "seconds";
            default "40";
            description "Time OSPF waits without receiving Hello packets before declaring a neighbor down";
        }

        leaf retransmit-interval {
            type uint32 {
                range "1..1800";
            }
            units "seconds";
            default "5";
            description "Time before OSPF retransmits an unacknowledged LSA to a neighbor";
        }

        leaf transit-delay {
            type uint32 {
                range "1..1800";
            }
            units "seconds";
            default "1";
            description "Time required to transmit an LSA on the interface, virtual link, or sham link";
        }

        container authentication {
            description
               "Container with authentication options that apply to all peers in this peer-group";
            leaf keychain {
                description
                    "Reference to a keychain. The keychain type must be ospf";
                type leafref {
                    path "/srl_nokia-system:system/srl_nokia-keychains:authentication/srl_nokia-keychains:keychain/srl_nokia-keychains:name";
                }
                must '/srl_nokia-system:system/srl_nokia-keychains:authentication/srl_nokia-keychains:keychain[srl_nokia-keychains:name = current()]' + '/srl_nokia-keychains:type = "ospf"'
                {
                    error-message "Only keychain of type ospf can be assigned";
                }
            }
        }

        container failure-detection {
            description
                "Options related to methods of detecting BGP session failure";
            leaf enable-bfd {
                description
                "Enables the use of BFD for livliness detection";
                type boolean;
                default "false";
            }
        }

        uses ospf-neighbor-state;
    }       // ospf-interface-config

    grouping ospf-interface-state {
        leaf type {
            config false;
            description "the value of type indicates the operational OSPF interface type.";
            type srl_nokia-ospf-types:interface-type;
        }
        leaf oper-state {
            config false;
            description "the OSPF interface state.";
            type enumeration {
                enum down { value 1; }
                enum loopback { value 2; }
                enum waiting { value 3; }
                enum point-to-point { value 4; }
                enum designated-router { value 5; }
                enum backup-designated-router { value 6; }
                enum other-designated-router { value 7; }
            }
        }
        leaf oper-mtu {
            config false;
            description "the value of oper-MTU indicates the operational size of the largest packet which can be sent/received on this OSPF interface, specified in octets. this size DOES include the underlying IP header length, but not the underlying layer headers/trailers.";
            type int32;
        }
        leaf oper-metric {
            config false;
            description "the value of metric-value indicates the metric value this interface is using. the default value of the metric is (reference bandwidth / if-speed). the value of the reference bandwidth is configured by the reference-bandwidth object.";
            type int32 {
                range "0..65535";
            }
        }
        leaf dr-id {
            config false;
            description "the value of DR-id indicates the router ID of the designated router.";
            type yang:dotted-quad;
        }
        leaf bdr-id {
            config false;
            description "the value of BDR-id indicates the router ID of the backup designated router.";
            type yang:dotted-quad;
        }
        leaf last-enabled-time {
            config false;
            description "the value of last-enabled-time indicates the sys-up-time value when ospf-if-admin-stat was last set to enabled (1) to run the ospf on this interface.";
            type yang:date-and-time;
        }
        leaf neighbor-count {
            config false;
            description "The total number of OSPF neighbors adjacent on this interface, in a state of INIT or greater, since admin-state was last set to 'enabled'.";
            type yang:gauge32;
        }
        leaf local-ip-address {
            config false;
            description "the value of local-ip-address indicates the IP address of this OSPF interface.";
            type yang:dotted-quad;
        }
        leaf link-lsa-cksum-sum {
            config false;
            description "the value of link-lsa-cksum-sum indicates the 32-bit unsigned sum of the link-scope link-state advertisements' LS checksums contained in this link's link-state database. the sum can be used to determine if there has been a change in a router's link-state database, and to compare the link state database of two routers.";
            type int32;
        }
        leaf link-lsa-count {
            config false;
            description "the value of link-lsa-count indicates the total number of link-scope link-state advertisements in this link's link-state database.";
            type yang:gauge32;
        }
    } // ospf-interface-state

    grouping ospf-interface-statistics {
        leaf events {
            config false;
            description "the value of events indicates the number of times this OSPF interface has changed its state, or an error has occurred.";
            type yang:counter32;
        }
        leaf last-event-time {
            config false;
            description "the value of last-event-time indicates the value of sys-up-time when an event was last associated with this OSPF interface.";
            type srl_nokia-comm:date-and-time;
        }
    }   // ospf-interface-statistics

    grouping ospf-interface-packet-counts {
        container packets {
            config false;
            description "Packet counters";
            leaf tx-total {
                config false;
                description "The total number of OSPF packets transmitted since admin-state was last set to 'enabled'.";
                type yang:counter32;
            }
            leaf tx-hello {
                config false;
                description "The total number of OSPF hello packets transmitted since admin-state was last set to 'enabled'.";
                type yang:counter32;
            }
            leaf tx-db-description {
                config false;
                description "The total number of OSPF database description packets transmitted since admin-state was last set to 'enabled'.";
                type yang:counter32;
            }
            leaf tx-ls-request {
                config false;
                description "The total number of OSPF link state requests (LS-rs)transmitted since admin-state was last set to 'enabled'.";
                type yang:counter32;
            }
            leaf tx-ls-update {
                config false;
                description "The total number of OSPF link state updates (LS-us) transmitted since admin-state was last set to 'enabled'.";
                type yang:counter32;
            }
            leaf tx-ls-ack {
                config false;
                description "The total number of OSPF link state acknowledgements transmitted since admin-state was last set to 'enabled'.";
                type yang:counter32;
            }
            leaf rx-total {
                config false;
                description "The total number of OSPF packets received since admin-state was last set to 'enabled'.";
                type yang:counter32;
            }
            leaf rx-hello {
                config false;
                description "The total number of OSPF hello packets received since admin-state was last set to 'enabled'.";
                type yang:counter32;
            }
            leaf rx-db-description {
                config false;
                description "The total number of OSPF database description packets received since admin-state was last set to 'enabled'.";
                type yang:counter32;
            }
            leaf rx-ls-request {
                config false;
                description "The total number of link state requests (LS-rs) received since admin-state was last set to 'enabled'.";
                type yang:counter32;
            }
            leaf rx-ls-update {
                config false;
                description "The total number of link state updates (LS-us) received since admin-state was last set to 'enabled'.";
                type yang:counter32;
            }
            leaf rx-ls-ack {
                config false;
                description "The total number of link state acknowledgements received since admin-state was last set to 'enabled'.";
                type yang:counter32;
            }
            leaf discarded {
                config false;
                description "The total number of OSPF packets discarded since admin-state was last set to 'enabled'.";
                type yang:counter32;
            }
            leaf retransmits {
                config false;
                description "The total number of OSPF retransmits since admin-state was last set to 'enabled'.";
                type yang:counter32;
            }
        }

        container bad-packets {
            config false;
            description "Bad packets counters";
            leaf bad-version {
                config false;
                description "The total number of OSPF packets received with bad OSPF version numbers since admin-state was last set to 'enabled'.";
                type yang:counter32;
            }
            leaf bad-network {
                config false;
                description "The total number of OSPF packets received with invalid network or mask since admin-state was last set to 'enabled'.";
                type yang:counter32;
            }
            leaf bad-area {
                config false;
                description "The total number of OSPF packets received with an area mismatch since admin-state was last set to 'enabled'.";
                type yang:counter32;
            }
            leaf bad-dest-address {
                config false;
                description "The total number of OSPF packets received with the incorrect IP destination address since admin-state was last set to 'enabled'.";
                type yang:counter32;
            }
            leaf bad-neighbors {
                config false;
                description "The total number of OSPF packets received where the neighbor information does not match the information this router has for the neighbor since admin-state was last set to 'enabled'.";
                type yang:counter32;
            }
            leaf bad-packet-type {
                config false;
                description "The total number of OSPF packets received with an invalid OSPF packet type since admin-state was last set to 'enabled'.";
                type yang:counter32;
            }
            leaf bad-length {
                config false;
                description "The total number of OSPF packets received with a total length not equal to the length given in the packet itself since admin-state was last set to 'enabled'.";
                type yang:counter32;
            }
            leaf bad-hello-interval {
                config false;
                description "the value of bad-hello-intervals indicates the total number of OSPF packets received where the hello interval given in packet was not equal to that configured on this interface since admin-state was last set to 'enabled'.";
                type yang:counter32;
            }
            leaf bad-dead-interval {
                config false;
                description "The total number of OSPF packets received where the dead interval given in the packet was not equal to that configured on this interface since admin-state was last set to 'enabled'.";
                type yang:counter32;
            }
            leaf bad-options {
                config false;
                description "The total number of OSPF packets received with an option that does not match those configured for this interface or area since admin-state was last set to 'enabled'.";
                type yang:counter32;
            }
            leaf bad-checksum {
                config false;
                description "The count of LS-as received with bad checksums.";
                type yang:counter32;
            }
            leaf bad-auth-type {
                config false;
                description "The total number of OSPF packets received with an invalid authorization type since admin-state was last set to 'enabled'.";
                type yang:counter32;
            }
            leaf bad-virtual-link {
                config false;
                description "The total number of OSPF packets received that are destined to a virtual link that does not exist since admin-state was last set to 'enabled'.";
                type yang:counter32;
            }
        }
    }   // ospf-interface-packet-counts

    grouping ospf-area-structure {
        leaf advertise-router-capability {
            type boolean;
            default "true";
            description "Allow router advertisement capabilities";
        }

        leaf blackhole-aggregate {
            description "Enables the creation of a blackhole for generated aggregates";
            type boolean;
        }

        leaf export-policy {
            must "(../area-id != '0.0.0.0')" {
                error-message "Export-policy is not allowed in area 0.0.0.0";
            }
            description
                "Apply an export policy to redistribute non-OSPFv2 routes into OSPF";
            type leafref {
                path "/srl-rpol:routing-policy/srl-rpol:policy/srl-rpol:name";
            }
        }

        container stub {
            presence "Configure this area as an OSPF stub area";
            must "not(../nssa)" {
               error-message "OSPF Area can not be configured as NSSA and stub simultaneously";
            }
            must "(../area-id != '0.0.0.0')" {
               error-message "OSPF backbone Area can not be configured as stub";
            }

            leaf default-metric{
                description
                    "Defines the default OSPF metric for associated stub area";
                type srl_nokia-ospf-types:ospf-metric;
            }
            leaf summaries {
                description
                    "Enables sending summary (type 3) advertisements into a stub area or Not 
                    So Stubby Area (NSSA) on an Area Border Router (ABR)";
                type boolean;
            }
        }

        container nssa {
            presence "Configure this area as an OSPF NSSA area";
            must "(../area-id != '0.0.0.0')" {
               error-message "OSPF backbone Area can not be configured as NSSA";
            }
            description
                "This command creates the context to configure the associated OSPF or OSPF3 
                area as Not So Stubby Area (NSSA).

                NSSAs are similar to stub areas in that no external routes are imported into 
                the area from other OSPF areas. The major difference between a stub area and 
                an NSSA is an NSSA has the capability to flood external routes that it 
                learns throughout its area and via an ABR to the entire OSPF or OSPF3 domain.";

            leaf redistribute-external {
                description
                    "Enables the redistribution of external routes into the Not So Stubby Area
                    (NSSA) or an NSSA area border router (ABR) that is exporting the routes 
                    into non-NSSA areas";
                type boolean;
            }
            leaf summaries {
                description
                    "Enables sending summary (type 3) advertisements into a stub area or Not 
                    So Stubby Area (NSSA) on an Area Border Router (ABR)";
                type boolean;
            }

            list area-range {
                key "ip-prefix-mask";
                description "Enter the area-range context";

                leaf ip-prefix-mask {
                    type srl_nokia-comm:ipv4-prefix;
                    description
                        "ip-prefix a.b.c.d (host bits must be 0)
                            mask [0..32]";
                }

                leaf advertise {
                    type boolean;
                    default "true";
                    description "Advertise summarized range of addresses to other areas";
                }
            }   // area-range list

            container originate-default-route {
                presence "Enable/disable generation of default route and its LSA type (3 or 7) into the NSSA";
                description "Enter the originate-default-route context";

                leaf type-nssa {
                    type boolean;
                    default "false";
                    description "Generate a default route using NSSA-LSA type";
                }

                leaf adjacency-check {
                    type boolean;
                    default "true";
                    description "Default route to remove if there is no adjacency";
                }

            } // container originate-default-route  
        }    // container nssa

        list area-range {
            key "ip-prefix-mask";
            description "Enter the area-range context";

            leaf ip-prefix-mask {
                type srl_nokia-comm:ipv4-prefix;
                description
                    "ip-prefix a.b.c.d (host bits must be 0)
                        mask [0..32]";
            }

            leaf advertise {
                type boolean;
                default "true";
                description "Advertise summarized range of addresses to other areas";
            }
        } // area-range list
    }

    grouping ospf-global-timers {
        container timers {
            description "Enter the timers context";
            leaf incremental-spf-wait {
                type uint32 {
                    range "0..1000";
                }
                default "1000";
                description "Delay time before an incremental SPF calculation is started";
            }

            leaf lsa-accumulate {
                type uint32 {
                    range "0..1000";
                }
                default "1000";
                description "Delay time for accumulating multiple LSAs before advertising them to neighbors";
            }

            leaf lsa-arrival {
                type uint32 {
                    range "0..600000";
                }
                default "1000";
                description "Minimum delay between receipt of the same LSAs arriving from neighbors";
            }

            leaf redistribute-delay {
                type uint32 {
                    range "0..1000";
                }
                default "1000";
                description "Hold down timer for external routes that are redistributed in OSPF";
            }

            container lsa-generate {
                description "Enter the lsa-generate context";
                leaf max-lsa-wait {
                    type uint32 {
                        range "10..600000";
                    }
                    units "milliseconds";
                    default "5000";
                    description "Maximum time between two consecutive occurrences of an LSA being generated";
                }

                leaf lsa-initial-wait {
                    type uint32 {
                        range "10..600000";
                    }
                    units "milliseconds";
                    default "5000";
                    description "First waiting period between link state advertisements LSA originates";
                }

                leaf lsa-second-wait {
                    type uint32 {
                        range "10..600000";
                    }
                    units "milliseconds";
                    default "5000";
                    description "Hold time between the first and second LSA generation";
                }

            } // container lsa-generate}

            container spf-wait {
                description "Enter the spf-wait context";

                leaf spf-max-wait {
                    type uint32 {
                        range "10..120000";
                    }
                    units "milliseconds";
                    default "10000";
                    description "Maximum interval between two consecutive SPF calculations";
                }

                leaf spf-initial-wait {
                    type uint32 {
                        range "10..100000";
                    }
                    units "milliseconds";
                    default "1000";
                    description "Initial SPF calculation delay after a topology change";
                }

                leaf spf-second-wait {
                    type uint32 {
                        range "10..100000";
                    }
                    units "milliseconds";
                    default "1000";
                    description "Hold time between the first and second SPF calculation";
                }

            } // container spf-wait
        } // container timers
    }

    grouping ospf-global-top {
        description
            " OSPF v2 Global parameters";

        leaf admin-state {
            description
                "Used to administratively enable or disable the OSPF instance";
            type srl_nokia-comm:admin-state;
            default "disable";
        }

        leaf version {
            mandatory true;
            description
                "The version that this ospf instance supports.";
            type identityref {
                base "srl_nokia-ospf-types:OSPF_VERSION";
            }
            must "not(. = 'srl_nokia-ospf-types:OSPF_V3'
                    and ../address-family != 'srl_nokia-ospf-types:IPV4_UNICAST'
                    and ../address-family != 'srl_nokia-ospf-types:IPV6_UNICAST' )" {
                error-message "OSPF_V3 must have address family defined";
            }
        }

        leaf address-family {
            description
                "The address family that this instance supports. 
                 Only valid for OSPFv3.";
            type identityref {
                base "srl_nokia-ospf-types:OSPFV3_ADDRESS_FAMILY";
            }
            must "not(../version = 'srl_nokia-ospf-types:OSPF_V2')" {
                error-message "OSPF_V2 does not support address-family";
            }
        }

        leaf router-id {
            type yang:dotted-quad;
        }

        leaf max-ecmp-paths {
            description
                "The maximum number of ECMP next-hops to program into the FIB 
                 for every IP prefix";
            type srl_nokia-ospf-types:ospf-ecmp;
            default "1";
        }

        leaf advertise-router-capability {
            description
                "Scope to advertise router-capability.";
            type enumeration {
                enum "false"                        { value 0; }
                enum "link"                         { value 1; }
                enum "area"                         { value 2; }
                enum "as"                           { value 3; }
            }
        }

        leaf export-policy {
            description
                "Apply an export policy to redistribute non-OSPFv2 routes into OSPF";
            type leafref {
                path "/srl-rpol:routing-policy/srl-rpol:policy/srl-rpol:name";
            }
        }

        leaf log-adjacency-changes {
            type boolean;
        }

        container asbr {
            presence "Configure the router as an ASBR (Autonomous System Boundary Router)";
            description "Configure the router as an ASBR (Autonomous System Boundary Router)";

            leaf trace-path {
                type union {
                    type int32 {
                        range "0..31";
                    }
                    type enumeration {
                        enum "none"                         { value -1; }
                    }
                }
                default "none";
                description "Domain identity";
            }
        }

        container export-limit {
            presence "Maximum number of routes (prefixes) that can be exported into OSPF from the route table";
            description "Enter the export-limit context";

            leaf number {
                type uint32 {
                    range "1..max";
                }
                mandatory true;
                description "Maximum number of routes or prefixes to be exported into IGP instance from route table";
            }

            leaf log-percent {
                type uint32 {
                    range "1..100";
                }
                description "Export limit at which warning a log message and SNMP notification are sent";
            }
        }

        leaf external-preference {
            description
                "Configure the route preference associated with OSPF external routes";
            type uint8;
            default 150;
        }

        container external-db-overflow {
            presence "Limit on number of AS-external-LSAs in LSDB and wait time before processing these if limit is exceeded";
            leaf interval {
                description
                    "";
                type uint32 {
                    range "0..2147483647";
                }
                default 0;
                units "seconds";
            }

            leaf limit {
                type uint32 {
                    range "0..2147483647";
                }
                default 0;
            }
        }

        container graceful-restart {
            description
                "Container for options related to OSPFv2 graceful restart";

            leaf helper-mode {
                description
                    "Enable or disable the IS-IS graceful restart helper function
                    When this leaf is set, the local system supports retaining
                    forwarding information during a neighbor router's restart.";
                type boolean;
                default false;
            }
            leaf strict-lsa-checking {
                description
                    "";
                type boolean;
                default false;
            }
        }

        leaf reference-bandwidth {
            description
                "Configures the reference bandwidth that provides the basis for
                interface metrics based on link Bandwidth

                If the reference bandwidth is defined, then the cost is calculated
                using the following formula:
                    cost = reference-bandwidth / bandwidth

                When a large reference-bandwidth value is configured, a metric
                calculation may result in a value higher than the supported protocol
                cost value. If this occurs, OSPFv2 automatically reverts to the
                maximum configurable cost metric.

                If the reference bandwidth is not configured then all interfaces
                have a default metric of 10.

                Note: To use metrics in excess of 63, wide metrics must be deployed";
            type uint64 {
                range "1..100000000";
            }
            units "kbps";
        }

        leaf preference {
            description
                "Sets the route prefence for OSPF sourced routes";
            type uint8{
                range "1..255";
            }
            default 10;
        }

        container overload {
            leaf active {
                type boolean;
                default false;
            }

            leaf overload-include-ext-1{
                type boolean;
                default false;
            }

            leaf overload-include-ext-2{
                type boolean;
                default false;
            }

            leaf overload-include-ext-stub{
                type boolean;
                default false;
            }

            container overload-on-boot {
                presence "Configure Overload-on-boot";
                leaf timeout {
                    type uint32 {
                        range "1..1800";   //ospf 1-1800; ospfv3 60-1800
                    }
                    default 60;
                    units "seconds";
                }
            }

            container rtr-adv-lsa-limit{
                leaf log-only {
                    type boolean;
                }
                leaf max-lsa-count {
                    type uint32{
                        range "1..4294967295";
                    }
                }
                leaf overload-timeout {
                    type union{
                        type uint16 {
                        range "1..1800";
                        // add "forever"
                        }
                    }
                }
                leaf warning-threshold {
                    type srl_nokia-comm:percentage;
                    default 0;
                }
            }

        }

        uses ospf-global-timers;
    } //ospf-global-top

    grouping ospf-global-state {
        leaf oper-state {
            config false;
            description
                "Used to report operational state of the OSPF instance";
            type srl_nokia-comm:admin-state;
        }
        leaf last-disabled-reason {
            config false;
            description "Reason why the disabled state was entered the last time.";
            type string {
                length 0..20;
            }
        }
        leaf oper-router-id {
            config false;
            description "the value of oper-router-id indicates the 32-bit integer used to uniquely
                         identify the router in the autonomous system. the default OSPF instance
                         will use the value specified by router-id or the one derived from the
                         IP layer. For the non-default instances of OSPF, this is the same value as
                         router-id, which must be specified before the OSPF instance can become
                         operational.";
            type yang:dotted-quad;
        }
        leaf area-border-router {
            config false;
            description "This indicates whether this router is an area border router.";
            type boolean;
        }
        leaf as-border-router {
            config false;
            description "This indicates whether this router is an AS border router.";
            type boolean;
        }
        leaf backbone-router {
            config false;
            description "This indicates whether or not this router is configured as an OSPF back bone router.";
            type boolean;
        }

        leaf overload-state {
            config false;
            description "the value of overload-oper-state indicates whether or not the OSPF application is presently in overload state or not.";
            type enumeration {
                enum overload { value 1;}
                enum no-overload { value 2;}
            }
        }
        leaf overload-rem-interval {
            config false;
            description "the value of overload-rem-interval indicates the time for which the system will be in overload state if OSPF is in overload state. the value of 0 implies that the system is indefinitely in overload state.";
            type int32 {
                range "0..65535";
            }
            units seconds;
        }
        leaf last-overload-entered-time {
            config false;
            description "the value of last-overload-entrd-time indicates the time at which the system last went into overload state.";
            type srl_nokia-comm:date-and-time;
        }
        leaf last-overload-exit-time {
            config false;
            description "the value of last-overload-exit-time indicates the time at which the system last came out of overload state.";
            type srl_nokia-comm:date-and-time;
        }
        leaf last-overload-enter-code {
            config false;
            description "the value of last-overload-enter-code indicates the condition which caused OSPF to get into overload.";
            type enumeration {
                enum none { value 1; }
                enum spf-failed { value 2; }
                enum boot-overload { value 3; }
                enum manual-overload { value 4; }
                enum sfm-overload { value 5; }
                enum fib-add-fail { value 6; }
                enum rtm-add-fail { value 7; }
                enum rtr-adv-lsa-limit { value 8; }
            }
        }
        leaf last-overload-exit-code {
            config false;
            description "the value of last-overload-exit-code indicates the reason why OSPF came out of overload state the last time, since reset.";
            type enumeration {
                enum none { value 1; }
                enum bgp-sig-recv { value 2; }
                enum timer-expired { value 3; }
                enum manual-exit { value 4; }
                enum sfm-overload-done { value 5; }
            }
        }

        leaf overflow {
            config false;
            description "The value of in-overflow-state indicates the current overflow state (true/false).
                         This overflow state occurs when the number of non-default AS-external-LS-as
                         entries exceed the link-state database capability.";
            type boolean;
        }
        leaf last-overflow-entered-time {
            config false;
            description "The value of last-ovrflw-entered-time indicates the value of sys-up-time the last time we entered overflow state. this overflow state occurs when the number of non-default AS-external-LS-as entries exceed the link-state database capability.";
            type srl_nokia-comm:date-and-time;
        }
        leaf last-overflow-exit-time {
            config false;
            description "the value of last-overflow-exit-time indicates the value of sys-up-time the last time we exited overflow state. this overflow state occurs when the number of non-default AS-external-LS-as entries exceed the link-state database capability.";
            type srl_nokia-comm:date-and-time;
        }

        leaf last-enabled-time {
            config false;
            description "the value of last-enabled-time indicates the value of sys-up-time when admin-state was last set to 'enabled'. when admin-state is set to 'disabled', the OSPF counters are stopped when admin-state is reset to 'enabled', the counters are reset to zero.";
            type srl_nokia-comm:date-and-time;
        }
        leaf routes-submitted {
            config false;
            description "the value of routes-submitted indicates the number of routes submitted to the route table manager (RTM) by this instance of OSPF.";
            type yang:gauge32;
        }
        leaf total-exported-routes {
            config false;
            description "the value of total-exported-routes indicates the total number of routes exported into OSPF from the route table manager when an export policy is configured. value of total-exported-routes would be 0 when no export policy is configured.";
            type yang:gauge32;
        }

        leaf ovld-lsa-limit-rem-interval {
            config false;
            description "the value of ovld-lsa-limit-rem-interval indicates the remaining time in seconds for which the system will be in overload state due to advertising router LSA limit exceeded. the value of 0 implies that the system is either not in overload or indefinitely in overload state.";
            type int32 {
                range "0..65535";
            }
            units seconds;
        }

        container spf {
            config false;
            description "SPF related information";

            leaf full-spf-runs {
                config false;
                description "The total number of times that complete SPF has been run on the router since OSPF was last enabled.";
                type yang:counter32;
            }
            leaf ext-spf-runs {
                config false;
                description "The total number of times that only the external portion of the SPF has been run since OSPF was last enabled.";
                type yang:counter32;
            }
            leaf incremental-inter-spf-runs {
                config false;
                description "The total number of incremental SPF runs triggered by new or updated inter-area prefix or inter-area router LS-as.";
                type yang:counter32;
            }
            leaf incremental-ext-spf-runs {
                config false;
                description "The total number of incremental SPF runs triggered by new or updated external LS-as.";
                type yang:counter32;
            }
            leaf spf-attempts-failed {
                config false;
                description "The number of times an attempt to run SPF has failed because SPF runs have been stopped as a result of insufficient memory resources.";
                type yang:counter32;
            }

            leaf max-spf-run-interval {
                config false;
                description "the value of max-spf-run-interval indicates the maximum time, in hundredths of seconds, used to perform a total SPF calculation.";
                type int32 {
                  range "0..2147483647";
                }
                units centiseconds;
            }
            leaf min-spf-run-interval {
                config false;
                description "the value of min-spf-run-interval indicates the minimum time, in hundredths of seconds, used to perform a total SPF calculation.";
                type int32 {
                  range "0..2147483647";
                }
                units centiseconds;
            }
            leaf avg-spf-run-interval {
                config false;
                description "the value of avg-spf-run-interval indicates the average time, in hundredths of seconds, of all the total SPF calculations performed by this OSPF router.";
                type int32 {
                  range "0..2147483647";
                }
                units centiseconds;
            }

            container last-full-spf {
                config false;
                description "Information about the last full SPF run";

                leaf run-time {
                    config false;
                    description "the value of last-full-spf-run-time indicates the time at which the system last performed a full dijkstra (SPF) run.";
                    type srl_nokia-comm:date-and-time;
                }
                leaf total-time {
                    config false;
                    description "Time it toook, in hundredths of seconds, to complete the last SPF run completely.";
                    type int32 {
                      range "0..2147483647";
                    }
                    units centiseconds;
                }
                leaf intra-spf-time {
                    config false;
                    description "Time it toook, in hundredths of seconds, to complete the intra-area SPF calculations.";
                    type int32 {
                      range "0..2147483647";
                    }
                    units centiseconds;
                }
                leaf inter-spf-time {
                    config false;
                    description "Time it toook, in hundredths of seconds, to complete the inter-area SPF calculations.";
                    type int32 {
                      range "0..2147483647";
                    }
                    units centiseconds;
                }
                leaf extern-spf-time {
                    config false;
                    description "Time it toook, in hundredths of seconds, to complete the external LSA calculations.";
                    type int32 {
                      range "0..2147483647";
                    }
                    units centiseconds;
                }
                leaf rtm-update-time {
                    config false;
                    description "Time it toook, in hundredths of seconds, to complete the RTM updates.";
                    type int32 {
                      range "0..2147483647";
                    }
                    units centiseconds;
                }
            }

            container last-ext-spf {
                config false;
                description "Information about the last external SPF run";
                leaf run-time {
                    config false;
                    description "the value of last-ext-spf-run-time indicates the value of sys-up-time when the external OSPF dijkstra (SPF) was last run.";
                    type srl_nokia-comm:date-and-time;
                }
                leaf interval {
                    config false;
                    description "the value of ext-spf-run-interval indicates the time, in hundredths of seconds, used to perform the most recent total external (not incremental) SPF calculation.";
                    type int32 {
                      range "0..2147483647";
                    }
                    units centiseconds;
                }
            }
        }
    } //ospf-global-state

    grouping ospf-top {
        description
            "Top-level OSPF configuration and operational state";

        container ospf {
            presence "Configure OSPFv2";
            description
                "Top-level configuration and operational state for
                Open Shortest Path First (OSPF) v2";
            must "not(../../type = 'srl_nokia-netinst:mac-vrf')" {
                error-message "OSPF configuration is not possible on network-instance of type mac-vrf ";
            }

            list instance {
                max-elements 3;
                description
                    "List of OSPFv2 protocol instances associated with this
                     network-instance.";

                key "name";

                leaf name {
                    description
                        "The name of the OSPFv2 instance";
                         type srl_nokia-comm:name;
                }
                
                uses ospf-global-top;
                uses ospf-global-state;

                list area {
                    key "area-id";

                    description
                        "The OSPFv2 areas within which the local system exists";

                    leaf area-id {
                        type srl_nokia-ospf-types:ospf-area-identifier;
                        description
                                "the area identifier as a dotted-quad.";
                    }

                    uses ospf-area-structure;

                    list interface {
                        description "List of OSPFv2 interfaces";
                        key "interface-name";
                        uses ospf-interface-key;

                        uses ospf-interface-config;

                        uses ospf-interface-state;
                        uses ospf-interface-statistics;
                        uses ospf-interface-packet-counts;

                        must "dead-interval >= (2 * hello-interval)" {
                            error-message "The dead-interval must be at least twice the hello-interval";
                        }
                    }
                    uses ospf-lsdb-structure;
                }
            }
        }
    }

    augment "/srl_nokia-netinst:network-instance/srl_nokia-netinst:protocols" {
        uses ospf-top;
    }
}

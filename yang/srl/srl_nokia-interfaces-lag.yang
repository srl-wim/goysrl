module srl_nokia-interfaces-lag {
  yang-version 1.1;

  // namespace
  namespace "urn:srl_nokia/interfaces/lags";

  prefix "srl_nokia-if-lag";

  import srl_nokia-features { prefix srl_nokia-feat; }
  import srl_nokia-interfaces { prefix srl_nokia-if; }
  import srl_nokia-common { prefix srl_nokia-comm; }

  description
    "Model for managing LAGs

     This model describes management of LAG parameters under SRL Interfaces";

  // identity statements

  // typedef statements

  revision 2020-06-30 {
    description
      "SRLinux 20.6.1";
  }

  typedef lag-type {
    type enumeration {
      enum lacp {
        description "LAG managed by LACP";
      }
      enum static {
        description "Statically configured bundle / LAG";
      }
    }
    description
      "Type to define the lag-type, i.e., how the LAG is
      defined and managed";
  }

  typedef member-link-oper-down-reason {
    type enumeration {
      enum "port-admin-disabled";
      enum "port-oper-disabled";
      enum "lag-admin-disabled";
      enum "lacp-down";
      enum "microBFD-down";
      enum "lag-min-link-threshold";
      enum "other";
    }
  }
  
	// Groupings
	
	grouping lag-ethernet-id-config {
		leaf lag-id {
			description
    		"Reference ID for associated LAG interface
      		Example: lag2 ";
      type leafref {
      	path "/srl_nokia-if:interface/srl_nokia-if:name";
      }
		}
	
	}

	grouping lag-logical-config {
  	description
      "Configuration data for aggregate interfaces";
		container lag {
			presence "Enable LAG configuration";
                        if-feature srl_nokia-feat:lag;
			description
			"Container for options related to LAG";
			must "starts-with(../srl_nokia-if:name,'lag')" {
                            error-message "lag container can only be configured on LAG interfaces";
                        }
			leaf lag-type {
                                must ".='static' or (.='lacp' and ../lacp)" {
                                    error-message "lacp container must be configured when lag-type is lacp";
                                }
				type lag-type;
                                default static;
				description
					"Sets the type of LAG, i.e., how it is
					configured / maintained";
			}
			leaf min-links {
				type uint16 {
                                    range 1..64;
                                }
                                default 1;
				description
					"Specifies the mininum number of member
					interfaces that must be active for the aggregate interface
					to be available";
			}
			leaf lag-speed {
				config false;
				type uint32;
                                units Mbps;
				description "Reports current aggregate bandwidth speed of the associated LAG";
			}
			list members {
				key "name";
				config false;
				description "Reports the list of interfaces associated with the LAG instance";
				leaf name {
					type leafref {
						path "/srl_nokia-if:interface/srl_nokia-if:name";
					}
				
				}
                                leaf oper-state {
                                        config false;
                                        description "Operational state for the associated LAG";
                                        type srl_nokia-comm:oper-state;
                                }
                                leaf oper-down-reason {
                                        config false;
                                        description "Reason for operational down state for the associated LAG";
                                        type member-link-oper-down-reason;
                                }
                                leaf microbfd-enabled {
                                  config false;
                                  type boolean;
                                  description
                                    "Indicates if microBFD is currently used in the determination of the member-link oper-status";
                                }
			}
    }
  }

  augment "/srl_nokia-if:interface" {
    uses lag-logical-config;
  }
}
